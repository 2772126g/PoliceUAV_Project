# UAV_Requirements 

## Stakeholder / Mission (Container)

### REQ-001: Search capability (Functional)
UAV shall locate missing persons in rural and urban environments

### REQ-002: Video streaming (Functional)
| UAV shall provide real-time video to ground operator |
| --- |

### REQ-003: Operator usability (Functional)
| \| UAV shall allow a single operator to control or monitor mission \| \| --- \| |
| --- |

## Performance (Container)

### REQ-010: Endurance (Functional)
| UAV shall fly for at least 40 minutes on a single battery charge |
| --- |

### REQ-011: Cruise speed (Functional)
| UAV shall maintain a cruise speed between 15–20 m/s |
| --- |

### REQ-012: Max payload (Functional)
UAV shall carry a payload of up to 2 kg

## Sensors & Data (Container)

### REQ-020: Camera resolution (Functional)
| UAV camera shall detect a human-sized object at 100 m |
| --- |

### REQ-021: GPS accuracy (Functional)
| UAV GPS position shall be accurate within ±2 m |
| --- |

### REQ-022: Sensor redundancy (Functional)
| UAV shall have at least 1 backup IMU for attitude sensing |
| --- |

## Control & Autonomy (Container)

### REQ-030: Manual control (Functional)
| UAV shall allow manual control of roll, pitch, yaw, and throttle |
| --- |

### REQ-031: Autonomous loiter (Functional)
| UAV shall loiter autonomously over a GPS waypoint |
| --- |

### REQ-032: Fail-safe behavior (Functional)
| UAV shall return-to-home within 5 seconds of GPS loss |
| --- |

## Safety & Reliability (Container)

### REQ-040: Low battery landing (Functional)
| UAV shall automatically land safely when battery reaches 20% |
| --- |

### REQ-041: Geofencing (Functional)
| UAV shall not exit pre-defined operational boundaries |
| --- |

### REQ-042: Weather tolerance (Functional)
| UAV shall operate safely in winds up to 10 m/s and light rain |
| --- |
